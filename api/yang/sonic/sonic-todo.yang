module sonic-todo {

  yang-version 1.1;

  namespace "http://github.com/Azure/sonic-todo";
  prefix todo;

  revision 2021-01-11 {
    description "First Revision";
  }

  container sonic-todo {
    container todo {
      list todo-list {
        key "name";
        
        leaf name {
          type string;
        }

        leaf json {
          type string;
        }
      }
    }
  }
}
