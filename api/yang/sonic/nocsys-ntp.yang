module accton-ntp {

  yang-version 1.1;

  namespace "http://github.com/accton/sonic-yang/accton-ntp";
  prefix ntp;

  import ietf-inet-types {
    prefix inet;
  }

  revision 2021-02-22 {
    description "First Revision";
  }

  container accton-ntp {
    container ntp {
      list ntp-list {
        key "ip";
        
        leaf ip {
          type inet:ipv4-address;
        }
        
        container state {
          leaf poll {
            type uint32;
          }
          
          leaf current {
            type string;
          }
        }
      }
    }
  }
}
