module accton-platform{

  yang-version 1.1;

  namespace "http://github.com/accton/sonic-yang/accton-platform";
  prefix platform;

  import accton-platform-types {
    prefix platform-types;
    revision-date 2021-02-22;
  }

  revision 2021-02-22 {
    description "First Revision";
  }

  grouping psu-config {
    description "Configuration data for power supply components";
    leaf enabled {
      description "Adminsitrative control on the on/off state of the power supply unit.";
      type boolean;
      default true;
    }
  }

  grouping platform-anchors-top {
    description "platform components";
    container power-supply {
      description "Data for power supply components";
      container config {
        description "Configuration data for power supply components";
        uses psu-config;
      }

      container state {
        config false;
        description "Operational state data for power supply components";
        uses psu-config;
      }
    }

    container fan {
      description "Data for fan components";
      container config {
        description "Configuration data for fan components";
      }

      container state {
        config false;
        description "Operational state data for fan components";
        leaf speed {
          description "Current (instantaneous) fan speed";
          type uint32;
          units rpm;
        }
      }
    }
  }
  
  grouping platform-properties-config {
    description "System-defined configuration data for component properties";
    leaf name {
      description "System-supplied name of the property";
      type string;
    }
    
    leaf value {
      description "Property values can take on a variety of types.";
      type union {
        type string;
        type boolean;
        type int64;
        type uint64;
        type decimal64 {
          fraction-digits 2;
        }
      }
    }
  }
  
  grouping platform-properties-state {
    description "Operational state data for component properties";
    leaf configurable {
      description "Indication whether the property is user-configurable";
      type boolean;
    }
  }
  
  grouping platform-properties-top {
    description "Top-level grouping";
    container properrties {
      description "Enclosing container";
      list property {
        description "List of system properties for the component";
        key "name";
        
        leaf name {
          description "Reference to the property name.";
          type leafref {
            path "../config/name";
          }
        }
        
        container config {
          description "Configuration data for each property";
          uses platform-properties-config;
        }
        
        container state {
          description "Operational state  data for each property";
          config false;
          uses platform-properties-config;
          uses platform-properties-state;
        }
      }
    }
  }
  
  grouping platform-component-config {
    description "Configuration data for components";
    leaf name {
      description "Device name for the component";
      type string;
    }
  }
  
  grouping platform-component-state {
    description "Operational state data for device components.";
    leaf type {
      description "Type of component as identified by the system";
      type union {
        type identityref {
          base platform-types:SONIC_HARDWARE_COMPONENT;
        }
        type identityref {
          base platform-types:SONIC_SOFTWARE_COMPONENT;
        }
      }
    }
    
    leaf serial-no {
      description "System-assigned serial number of the component.";
      type string;
    }
    
    leaf part-no {
      description "System-assigned part number for the component.";
      type string;
    }
    
    leaf hardware-version {
      description "For hardware components, this is the hardware revision of the component.";
      type string;
    }
    
    leaf software-version {
      description "For software components such as operating system or other
      software module, this is the version of the currently running software.";
      type string;
    }
    
    leaf mfg-name {
      description "System-supplied identifier for the manufacturer of the component.";
      type string;
    }
    
    leaf mfg-date {
      description "System-supplied representation of the component's manufacturing date.";
      type platform-types:date;
    }
  }
  
  grouping platform-component-temp-state {
    description "Temperature state data for device components";
    container temperature {
      description "Temperature in degrees Celsius of the component.";
      leaf instant {
        description "The instantaneous value of the statistic.";
        type decimal64 {
          fraction-digits 1;
        }
        units celsius;
      }
    }
  }
  
  container sonic-platform {
    container platform {
      description "Top-level container for the components in the system.";
      list component-list {
        description "List of components, keyed by component name.";
        key "name";
      
        leaf name {
          description "References the component name";
          type leafref {
            path "../config/name";
          }
        }
        
        container config {
          description "Configuration data for each component";
          uses platform-component-config;
        }
        
        container state {
          config false;
          description "State data for each component";
          uses platform-component-state;
          uses platform-component-temp-state;
        }
        
        uses platform-anchors-top;
        uses platform-properties-top;
      }
    }
  }
}
