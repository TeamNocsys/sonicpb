module accton-todo {

  yang-version 1.1;

  namespace "http://github.com/accton/sonic-yang/accton-todo";
  prefix todo;

  revision 2021-02-22 {
    description "First Revision";
  }

  container accton-todo {
    container todo {
      list todo-list {
        key "name";
        
        leaf name {
          type string;
        }

        leaf json {
          type string;
        }
      }
    }
  }
}
