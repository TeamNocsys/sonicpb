module accton-neighor {

  yang-version 1.1;

  namespace "http://github.com/accton/sonic-yang/accton-neighor";
  prefix neighor;
  
  import ietf-yang-types {
    prefix yang;
  }
  
  import accton-port {
    prefix port;
    revision-date 2021-02-22;
  }
  
  import accton-portchannel {
    prefix lag;
    revision-date 2021-02-22;
  }
  
  import accton-vlan {
    prefix vlan;
    revision-date 2021-02-22;
  }

  import accton-types {
    prefix stypes;
    revision-date 2021-02-22;
  }

  revision 2021-02-22 {
    description "First Revision";
  }

  container accton-neighor {
    container neighor {
      list neighor-list {
        key "name ip-prefix";
        
        leaf name {
          type union {
            type leafref {
              path /port:accton-port/port:port/port:port-list/port:port-name;
            }
            type leafref {
              path /lag:accton-portchannel/lag:portchannel/lag:portchannel-list/lag:portchannel-name;
            }
            type leafref {
              path /vlan:accton-vlan/vlan:vlan/vlan:vlan-list/vlan:vlan-name;
            }
          }
        }
        
        leaf ip-prefix {
          type union {
            type stypes:accton-ip4-prefix;
            type stypes:accton-ip6-prefix;
          }
        }
        
        leaf neigh {
          type yang:mac-address;
        }
      }
    }
  }
}
