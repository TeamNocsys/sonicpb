module accton-mdns {

  yang-version 1.1;

  namespace "http://github.com/accton/sonic-yang/accton-mdns";
  prefix mdns;
  
  import ietf-yang-types {
    prefix yang;
  }
  
  import accton-types {
    prefix stypes;
    revision-date 2021-02-22;
  }

  revision 2021-09-01 {
    description "First Revision";
  }

  container accton-mdns {
    container mdns {
      list mdns-list {
        key "ip-prefix";
        
        leaf ip-prefix {
          type union {
            type stypes:accton-ip4-prefix;
            type stypes:accton-ip6-prefix;
          }
        }
        
        leaf hostname {
          type string;
        }
      }
    }
  }
}
