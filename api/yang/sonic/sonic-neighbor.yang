module sonic-neighor {

  yang-version 1.1;

  namespace "http://github.com/Azure/sonic-neighor";
  prefix neighor;
  
  import ietf-yang-types {
    prefix yang;
  }
  
  import sonic-port {
    prefix port;
  }
  
  import sonic-portchannel {
    prefix lag;
  }
  
  import sonic-vlan {
    prefix vlan;
  }

  import sonic-types {
    prefix stypes;
  }

  revision 2021-01-11 {
    description "First Revision";
  }

  container sonic-neighor {

    container neighor {

      list neighor-list {

        key "name ip-prefix";

        leaf name {
          type union {
            type leafref {
              path /port:sonic-port/port:port/port:port-list/port:port-name;
            }
            type leafref {
              path /lag:sonic-portchannel/lag:portchannel/lag:portchannel-list/lag:portchannel-name;
            }
            type leafref {
              path /vlan:sonic-vlan/vlan:vlan/vlan:vlan-list/vlan:vlan-name;
            }
          }
        }

        leaf ip-prefix {
          type union {
            type stypes:sonic-ip4-prefix;
            type stypes:sonic-ip6-prefix;
          }
        }

        leaf neigh {
          type yang:mac-address;
        }
        
      }
    }
  }
}
