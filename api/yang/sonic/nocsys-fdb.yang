module accton-fdb {

  yang-version 1.1;

  namespace "http://github.com/accton/sonic-yang/accton-fdb";
  prefix fdb;
  
  import accton-port {
    prefix port;
  }

  revision 2021-02-22 {
    description "First Revision";
  }

  container accton-fdb {
    container fdb {
      list fdb-list {
        key "fdb-name";
        
        leaf fdb-name {
          type string {
            pattern 'Vlan([0-9]{1,3}|[0-3][0-9]{4}|[4][0][0-8][0-9]|[4][0][9][0-4])' 
                    + ':' + '[0-9a-fA-F]{2}(:[0-9a-fA-F]{2}){5}';
          }
        }
        
        leaf port {
          type leafref {
            path /port:accton-port/port:port/port:port-list/port:port-name;
          }
        }
        
        leaf type {
          type enumeration {
            enum STATIC;
            enum DYNAMIC;
          }
        }
      }
    }
  }
}
