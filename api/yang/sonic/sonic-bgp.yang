module sonic-bgp {

	yang-version 1.1;

	namespace "http://github.com/Azure/sonic-bgp";
	prefix bgp;

	import sonic-types {
		prefix stypes;
		revision-date 2019-07-01;
	}

	description "BGP yang Module for SONiC OS";

	revision 2021-01-11 {
		description "First Revision";
	}

	container sonic-bgp {

	    container bgp-neighbor {

	        description "BGP_NEIGHBOR part of config_db.json";

	        list bgp-neighbor-list {

				key "ip";

				ext:key-regex-configdb-to-yang "^([a-fA-F0-9:./]+)$";

				ext:key-regex-yang-to-configdb "<ip>";

				leaf ip {
				    type string {
				        pattern '(([0-9]|[1-9][0-9]|1[0-9][0-9]|2[0-4][0-9]|25[0-5])\.){3}([0-9]|[1-9][0-9]|1[0-9][0-9]|2[0-4][0-9]|25[0-5])';
				    }
				}

				leaf asn {
			        	type uint32 {
			            		range 1..65536;
			        	}
				}

				leaf name {
					type string {
						length 1..128;
					}
				}

				leaf local-addr {
			        	type leafref {
			            		path "/bgp:sonic-bgp/bgp:bgp-neighbor/bgp:bgp-neighbor-list/bgp:ip";
			        	}
				}

				leaf holdtime {
			        	type uint32 {
			            		range 1..65536;
			        	}
				}

				leaf keepalive {
			        	type uint32 {
			            		range 1..65536;
			        	}
				}

				leaf nhopself {
				    type boolean;
				}

				leaf rrclient {
				    type boolean;
				}

				leaf admin-status {
					type stypes:admin-status;
				}
	        }
	    }

	    container bgp-peer-range {

	        description "BGP_PEER_RANGE part of config_db.json";

	        list bgp-peer-range-list {

				key "peer-group-name";

				ext:key-regex-configdb-to-yang "^([a-zA-Z0-9_-]+)$";

				ext:key-regex-yang-to-configdb "<peer-group-name>";

				leaf peer-group-name {
					type string {
						length 1..128;
					}
				}

				leaf peer_asn {
			        	type uint32 {
			            		range 1..65536;
			        	}
				}

				leaf-list ip-range {
				    type stypes:sonic-ip4-prefix;
				}

				leaf src-addr {
			        	type leafref {
			            		path "/bgp:sonic-bgp/bgp:bgp-neighbor/bgp:bgp-neighbor-list/bgp:ip";
			        	}
				}
	        }
        }

	    container bgp-monitors {

	        description "BGP_MONITORS part of config_db.json";

	        list bgp-monitors-list {

				key "ip";

				ext:key-regex-configdb-to-yang "^([a-fA-F0-9:./]+)$";

				ext:key-regex-yang-to-configdb "<ip>";

				leaf ip {
			       		type leafref {
			            		path "/bgp:sonic-bgp/bgp:bgp-neighbor/bgp:bgp-neighbor-list/bgp:ip";
			        	}
				}

				leaf name {
					type string {
						length 1..128;
					}
				}
	        }
        }
	}
}
