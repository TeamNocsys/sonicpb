module accton-route {

  yang-version 1.1;

  namespace "http://github.com/Azure/sonic-route";
  prefix route;

  import ietf-inet-types {
    prefix inet;
  }

  import accton-port {
    prefix port;
	revision-date 2021-02-22;
  }

  import accton-types {
    prefix stypes;
    revision-date 2021-02-22;
  }

  import accton-vlan {
    prefix vlan;
    revision-date 2021-02-22;
  }

  import accton-vrf {
    prefix vrf;
    revision-date 2021-02-22;
  }

  revision 2021-02-22 {
    description "First Revision";
  }

    typedef ip-address-list {
        type union {
            type ipv4-address-list;
            type ipv6-address-list;
        }
        description
            "The ip-address-list type represents comma separated list of
             IP addresses and is IP version neutral. The format of the
             textual representation implies the IP version.";
    }

    typedef ipv4-address-list {
        type string {
            pattern
                '((([0-9]|[1-9][0-9]|1[0-9][0-9]|2[0-4][0-9]|25[0-5])\.){3}' +
                '([0-9]|[1-9][0-9]|1[0-9][0-9]|2[0-4][0-9]|25[0-5])' +
                '(%[\p{N}\p{L}]+)?,)*' +
                '(([0-9]|[1-9][0-9]|1[0-9][0-9]|2[0-4][0-9]|25[0-5])\.){3}' +
                '([0-9]|[1-9][0-9]|1[0-9][0-9]|2[0-4][0-9]|25[0-5])' +
                '(%[\p{N}\p{L}]+)?';
        }
        description
            "The ipv4-address-list type represents comma separated list
             of IPv4 addresses in dotted-quad notation. The IPv4 address
             may include a zone index, separated by a % sign.";
    }

    typedef ipv6-address-list {
        type string {
            pattern
                '(((:|[0-9a-fA-F]{0,4}):)([0-9a-fA-F]{0,4}:){0,5}' +
                '((([0-9a-fA-F]{0,4}:)?(:|[0-9a-fA-F]{0,4}))|' +
                '(((25[0-5]|2[0-4][0-9]|[01]?[0-9]?[0-9])\.){3}' +
                '(25[0-5]|2[0-4][0-9]|[01]?[0-9]?[0-9])))' +
                '(%[\p{N}\p{L}]+)?,)*' +
                '((:|[0-9a-fA-F]{0,4}):)([0-9a-fA-F]{0,4}:){0,5}' +
                '((([0-9a-fA-F]{0,4}:)?(:|[0-9a-fA-F]{0,4}))|' +
                '(((25[0-5]|2[0-4][0-9]|[01]?[0-9]?[0-9])\.){3}' +
                '(25[0-5]|2[0-4][0-9]|[01]?[0-9]?[0-9])))' +
                '(%[\p{N}\p{L}]+)?';
            pattern
                '(((([^:,]+:){6}(([^:,]+:[^:,]+)|([^,]*\.[^,]*)))|' +
                '((([^:,]+:)*[^:,]+)?::(([^:,]+:)*[^:,]+)?)' +
                '(%[^,]+)?),)*' +
                '((([^:,]+:){6}(([^:,]+:[^:,]+)|([^,]*\.[^,]*)))|' +
                '((([^:,]+:)*[^:,]+)?::(([^:,]+:)*[^:,]+)?)' +
                '(%[^,]+)?)';
        }
        description
            "The ipv6-address-list type represents comma separated list
             of IPv6 addresses in full, mixed, shortened, and shortend-
             mixed notation. The IPv6 address may include a zone index,
             separated by a % sign.";
    }

  container accton-route {
    container route {
      list route-list {
        key "vrf-name ip-prefix";

        leaf vrf-name {
          type leafref {
            path /vrf:accton-vrf/vrf:vrf/vrf:vrf-list/vrf:vrf-name;
          }
        }

        leaf ip-prefix {
          type union {
            type stypes:accton-ip4-prefix;
            type stypes:accton-ip6-prefix;
          }
        }

        leaf nexthop {
            type ip-address-list;
        }

        leaf ifname {
          type string;
          description
             "List of interface name for all next-hops of specific route.
             If interface is not in the current VRF, the nexthop-vrf field should match
             the vrf of this interface for routes to be configured.
             If interface not specified by the user empty string will be set to make
             the set";
        }
      }
    }
  }
}
