module accton-platform-types {

  yang-version "1.1";

  namespace "http://github.com/accton/sonic-yang/accton-platform-lldp-types";
  prefix platform-types;

  revision 2021-02-22 {
    description "First Revision";
  }

  typedef date {
    description "A full UTC date, expressed in the format described in RFC3339.";

    type string {
      pattern '^[0-9]{4}\-[0-9]{2}\-[0-9]{2}$';
    }
  }

  identity SONIC_HARDWARE_COMPONENT {   
    description "Base identity for hardware related components in a managed device.";
  }

  identity SONIC_SOFTWARE_COMPONENT {
    description "Base identity for software-related components in a managed device.";
  }

  identity POWER_SUPPLY {
    base SONIC_HARDWARE_COMPONENT;
    description "Component that is supplying power to the device";
  }

  identity FAN {
    base SONIC_HARDWARE_COMPONENT;
    description "Cooling fan, or could be some other heat-reduction components.";
  }

  identity SENSOR {
    base SONIC_HARDWARE_COMPONENT;
    description "Physical sensor, e.g., a temperature sensor in a  chassis";
  }

  identity OPERATING_SYSTEM {
    base SONIC_SOFTWARE_COMPONENT;
    description "Operating system running on a component";
  }
}
