module accton-interface {

  yang-version 1.1;

  namespace "http://github.com/accton/sonic-yang/accton-interface";
  prefix intf;

  import ietf-yang-types {
    prefix yang;
  }

  import ietf-inet-types {
    prefix inet;
  }

  import accton-types {
    prefix stypes;
    revision-date 2021-02-22;
  }

  import accton-port {
    prefix port;
    revision-date 2021-02-22;
  }
  
  import accton-vrf {
    prefix vrf;
    revision-date 2021-02-22;
  }

  description "INTERFACE yang Module for SONiC OS";

  revision 2021-02-22 {
    description "First Revision";
  }

  container accton-interface {
    container interface {
      list interface-list {
        key "port-name";
        
        leaf port-name {
          type leafref {
            path /port:accton-port/port:port/port:port-list/port:port-name;
          }
        }
        
        leaf vrf-name {
          type leafref {
            path /vrf:accton-vrf/vrf:vrf/vrf:vrf-list/vrf:vrf-name;
          }
        }
      }
      
      list interface-ipprefix-list {
        key "port-name ip-prefix";

        leaf port-name {
          type leafref {
            path /port:accton-port/port:port/port:port-list/port:port-name;
          }
        }
        
        leaf ip-prefix {
          type union {
            type stypes:accton-ip4-prefix;
            type stypes:accton-ip6-prefix;
          }
        }
        
        leaf scope {
          type enumeration {
            enum global;
            enum local;
          }
        }
        
        leaf family {
          type stypes:ip-family;
        }
      }
    }
  }
}
