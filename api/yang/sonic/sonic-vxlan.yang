module sonic-vxlan {

  yang-version 1.1;

  namespace "http://github.com/Azure/sonic-vxlan";
  prefix vxlan;

  import sonic-types {
    prefix stypes;
  }

  revision 2021-01-11 {
    description "First Revision";
  }

  container sonic-vxlan {
  
    container vxlan {
    
      list vxlan-tunnel-list {
      
        key "tunnel-name";
        
        leaf tunnel-name {
          type string {
            length 1..128;
          }
        }
        
        leaf src-ip {
          type stypes:sonic-ip4-prefix;
        }
        
        leaf dst-ip {
          type stypes:sonic-ip4-prefix;
        }
      }
      
      list vxlan-tunnel-map-list {
        key "tunnel-name tunnel-map";
        
        leaf tunnel-name {
          type leafref {
            path /vxlan:sonic-vxlan/vxlan:vxlan/vxlan:vxlan-tunnel-list/vxlan:tunnel-name;
          }
        }
        
        leaf tunnel-map {
          type string {
            length 1..128;
          }
        }
        
        leaf vni {
          type uint32;
        }
        
        leaf vlan {
          type leafref {
            path /vlan:sonic-vlan/vlan:vlan/vlan:vlan-list/vlan:vlanid;
          }
        }
      }
      
      list vnet-list {
        key "vnet-name";
        
        leaf vnet-name {
          type string {
            length 1..128;
          }
        }

        leaf vxlan-tunnel {
          type leafref {
            path /vxlan:sonic-vxlan/vxlan:vxlan/vxlan:vxlan-tunnel-list/vxlan:tunnel-name;
          }
        }

        leaf vni {
          type uint32;
        }

        leaf-list peer-list {
          type leafref {
            path /vxlan:sonic-vxlan/vxlan:vxlan/vxlan:vnet-list/vxlan:vnet-name;
          }
        }
      }

    }
  }
}
