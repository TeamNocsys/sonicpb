module accton-vxlan {

  yang-version 1.1;

  namespace "http://github.com/accton/sonic-yang/accton-vxlan";
  prefix vxlan;

  import accton-types {
    prefix stypes;
    revision-date 2021-02-22;
  }

  import accton-vlan {
    prefix vlan;
    revision-date 2021-02-22;
  }

  revision 2021-02-22 {
    description "First Revision";
  }

  container accton-vxlan {
    container vxlan {
      list vxlan-tunnel-list {
        key "tunnel-name";

        leaf tunnel-name {
          type string {
            length 1..128;
          }
        }

        leaf src-ip {
          type stypes:accton-ip4-prefix;
        }

        leaf dst-ip {
          type stypes:accton-ip4-prefix;
        }
      }

      list vxlan-tunnel-map-list {
        key "tunnel-name tunnel-map";

        leaf tunnel-name {
          type leafref {
            path /vxlan:accton-vxlan/vxlan:vxlan/vxlan:vxlan-tunnel-list/vxlan:tunnel-name;
          }
        }

        leaf tunnel-map {
          type string {
            length 1..128;
          }
        }

        leaf vni {
          type uint32;
        }

        leaf vlan {
          type leafref {
            path /vlan:accton-vlan/vlan:vlan/vlan:vlan-list/vlan:vlanid;
          }
        }
      }

      list vnet-list {
        key "vnet-name";

        leaf vnet-name {
          type string {
            length 1..128;
          }
        }

        leaf vxlan-tunnel {
          type leafref {
            path /vxlan:accton-vxlan/vxlan:vxlan/vxlan:vxlan-tunnel-list/vxlan:tunnel-name;
          }
        }

        leaf vni {
          type uint32;
        }

        leaf-list peer-list {
          type leafref {
            path /vxlan:accton-vxlan/vxlan:vxlan/vxlan:vnet-list/vxlan:vnet-name;
          }
        }
      }
    }
  }
}
