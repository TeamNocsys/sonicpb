module sonic-vrf {

  yang-version 1.1;

  namespace "http://github.com/Azure/sonic-vrf";
  prefix vrf;

  description "VRF yang Module for SONiC OS";

  revision 2021-01-11 {
    description "First Revision";
  }

  container sonic-vrf {

    container vrf {

      description "VRF part of config_db.json";

      list vrf-list {

        key "vrf-name";

        leaf vrf-name {
          type string {
            pattern 'Vrf[a-zA-Z0-9_-]+';
          }
        }

        leaf fallback {
          type boolean;
        }
      }
      /* end of VRF_LIST */
    }
    /* end of VRF container */
  }
  /* end of container sonic-vrf */
}
/* end of module sonic-vrf */
