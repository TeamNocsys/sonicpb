module accton-vrf {

  yang-version 1.1;

  namespace "http://github.com/accton/sonic-yang/accton-vrf";
  prefix vrf;

  revision 2021-02-22 {
    description "First Revision";
  }

  container accton-vrf {
    container vrf {
      list vrf-list {
        key "vrf-name";

        leaf vrf-name {
          type string {
            pattern 'Vrf[a-zA-Z0-9_-]+';
          }
        }

        leaf fallback {
          type boolean;
        }
      }
    }
  }
}
