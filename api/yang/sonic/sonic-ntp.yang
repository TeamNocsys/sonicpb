module sonic-ntp {

  yang-version 1.1;

  namespace "http://github.com/Azure/sonic-ntp";
  prefix ntp;

  import ietf-inet-types {
    prefix inet;
  }

  revision 2021-01-11 {
    description "First Revision";
  }

  container sonic-ntp {

    container ntp {

      list ntp-list {

        key "ip";

        leaf ip {
          type inet:ipv4-address;
        }

        container state {
          leaf poll {
            type uint32;
          }
          
          leaf current {
            type string;
          }
        }
      }
    }
  }
}
