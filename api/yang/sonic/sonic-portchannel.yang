module sonic-portchannel {

  yang-version 1.1;

  namespace "http://github.com/Azure/sonic-portchannel";
  prefix lag;

  import ietf-yang-types {
    prefix yang;
  }

  import ietf-inet-types {
    prefix inet;
  }

  import sonic-types {
    prefix stypes;
    revision-date 2019-07-01;
  }

  import sonic-extension {
    prefix ext;
    revision-date 2019-07-01;
  }

  import sonic-port {
    prefix port;
    revision-date 2019-07-01;
  }

  description "PORTCHANNEL yang Module for SONiC OS";

  revision 2019-07-01 {
    description "First Revision";
  }

  container sonic-portchannel {

    container portchannel {

      description "PORTCHANNEL part of config_db.json";

      list portchannel-list {

        key "portchannel-name";

        leaf portchannel-name {
          type string {
            length 1..128;
            pattern 'PortChannel[0-9]{1,4}';
          }
        }

        leaf min-links {
          type uint8 {
            range 1..128;
          }
        }

        leaf mtu {
          type uint16 {
            range 1..9216;
          }
        }

        leaf admin-status {
          type stypes:admin-status;
        }
      } /* end of list PORTCHANNEL_LIST */

    } /* end of container PORTCHANNEL */
    
    container portchannel-member {
      description "PORTCHANNEL_MEMBER part of config_db.json";
      
      list portchannel-member-list {
        key "portchannel-name port";
        
        leaf portchannel-name {
          type leafref {
            path "/lag:sonic-portchannel/lag:portchannel/lag:portchannel-list/lag:portchannel-name";
          }
        }

        leaf port {
          type leafref {
            path /port:sonic-port/port:port/port:port-list/port:port-name;
          }
        }
      }
      /* end of list PORTCHANNEL_MEMBER_LIST */
    }
    /* end of PORTCHANNEL_MEMBER container */

    container portchannel-interface {

      description "PORTCHANNEL_INTERFACE part of config_db.json";

      list portchannel-interface-list {

        key "portchannel-name";

        leaf portchannel-name {
          type leafref {
            path "/lag:sonic-portchannel/lag:portchannel/lag:portchannel-list/lag:portchannel-name";
          }
        }

        leaf vrf-name {
          type string {
            pattern "Vrf[a-zA-Z0-9_-]+";
            length 3..255;
          }
        }
      }
      /* end of PORTCHANNEL_INTERFACE_LIST */

      list portchannel-interface-ipprefix-list {

        key "portchannel-name ip-prefix";

        leaf portchannel-name {
          type leafref {
            path "/lag:sonic-portchannel/lag:portchannel/lag:portchannel-list/lag:portchannel-name";
          }
        }

        leaf ip-prefix {
          type union {
            type stypes:sonic-ip4-prefix;
            type stypes:sonic-ip6-prefix;
          }
        }

        leaf scope {
          type enumeration {
            enum global;
            enum local;
          }
        }

        leaf family {
          type stypes:ip-family;
        }
      }
      /* end of PORTCHANNEL_INTERFACE_IPPREFIX_LIST */
    }
    /* end of PORTCHANNEL_INTERFACE container */

  } /* end of container sonic-portchannel */

} /* end of module sonic-port */
