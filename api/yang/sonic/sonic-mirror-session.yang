module sonic-mirror-session {

  yang-version 1.1;

  namespace "http://github.com/Azure/sonic-mirror-session";
  prefix mirror;

  import sonic-port {
    prefix port;
    revision-date 2019-07-01;
  }

  import ietf-inet-types {
    prefix inet;
  }
  
  description "MIRROR_SESSION_TABLE yang Module for SONiC OS";

  revision 2021-01-11 {
    description "First Revision";
  }

  container sonic-mirror-session {

    container mirror-session {

      list mirror-session-list {

        key "name";

        leaf name {
          type string {
            length 1..255;
          }
        }

        leaf status {
          type enumeration {
            enum active;
            enum inactive;
          }
        }
        
        leaf src-ip {
          type inet:ip-address;
        }
        
        leaf dst-ip {
          type inet:ip-address;
        }
        
        leaf gre-type {
          type uint16;
        }
        
        leaf dscp {
          type inet:dscp;
        }
        
        leaf ttl {
          type uint8;
        }
        
        leaf queue {
          type uint8;
        }
        
        leaf policer {
          type string;
        }
        
        leaf dst-port {
          type leafref {
              path /port:sonic-port/port:port/port:port-list/port:port-name;
            }
        }
        
        leaf src-port {
          type leafref {
              path /port:sonic-port/port:port/port:port-list/port:port-name;
            }
        }
        
        leaf direction {
          type enumeration {
            enum RX;
            enum TX;
            enum BOTH;
          }
        }
        
        leaf type {
          type enumeration {
            enum SPAN;
            enum ERSPAN;
          }
        }
      }
      /* end of mirror-session-list */
    }
    /* end of mirror-session container */
  }
  /* end of container sonic-mirror-session */
}
/* end of module sonic-mirror-session */
