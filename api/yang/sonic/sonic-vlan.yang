module sonic-vlan {

  yang-version 1.1;

  namespace "http://github.com/Azure/sonic-vlan";
  prefix vlan;

  import ietf-yang-types {
    prefix yang;
  }

  import ietf-inet-types {
    prefix inet;
  }

  import sonic-types {
    prefix stypes;
    revision-date 2019-07-01;
  }

  import sonic-extension {
    prefix ext;
    revision-date 2019-07-01;
  }

  import sonic-port {
    prefix port;
    revision-date 2019-07-01;
  }

  description "VLAN yang Module for SONiC OS";

  revision 2019-07-01 {
    description "First Revision";
  }

  container sonic-vlan {

    container vlan {

      description "VLAN part of config_db.json";

      list vlan-list {

        key "vlan-name";

        leaf vlan-name {
          type string {
            pattern 'Vlan([0-9]{1,3}|[0-3][0-9]{4}|[4][0][0-8][0-9]|[4][0][9][0-4])';
          }
        }

        leaf vlanid {
          type uint16 {
            range 1..4094;
          }
        }

        leaf description {
          type string {
            length 1..255;
          }
        }

        leaf-list dhcp-servers {
          type inet:ip-address;
        }

        leaf mtu {
          type uint16 {
            range 1..9216;
          }
        }

        leaf admin-status {
          type stypes:admin-status;
        }

        leaf-list members {
          /* leaf-list members are unique by default */

          type leafref {
            path "/port:sonic-port/port:port/port:port-list/port:port-name";
          }
        }
      }
      /* end of VLAN_LIST */
    }
    /* end of container VLAN */

    container vlan-member {

      description "VLAN_MEMBER part of config_db.json";

      list vlan-member-list {

        key "vlan-name port";

        leaf vlan-name {
          type leafref {
            path "/vlan:sonic-vlan/vlan:vlan/vlan:vlan-list/vlan:vlan-name";
          }
        }

        leaf port {
          /* key elements are mandatory by default */
          type leafref {
            path /port:sonic-port/port:port/port:port-list/port:port-name;
          }
        }

        leaf tagging-mode {
          type enumeration {
            enum tagged;
            enum untagged;
            enum priority_tagged;
          }
        }
      }
      /* end of list VLAN_MEMBER_LIST */
    }
    /* end of container VLAN_MEMBER */
    
    container vlan-interface {

      description "VLAN_INTERFACE part of config_db.json";

      list vlan-interface-list {

        description "VLAN INTERFACE part of config_db.json with vrf";

        key "vlan-name";

        leaf vlan-name {
          type leafref {
            path /vlan:sonic-vlan/vlan:vlan/vlan:vlan-list/vlan:vlan-name;
          }
        }

        leaf vrf_name {
          type string {
            pattern "Vrf[a-zA-Z0-9_-]+";
            length 3..255;
          }
        }
      }
      /* end of VLAN_INTERFACE_LIST */

      list vlan-interface-ipprefix-list {

        key "vlan-name ip-prefix";

        leaf vlan-name {
          type leafref {
            path "/vlan:sonic-vlan/vlan:vlan/vlan:vlan-list/vlan:vlan-name";
          }
        }

        leaf ip-prefix {
          type union {
            type stypes:sonic-ip4-prefix;
            type stypes:sonic-ip6-prefix;
          }
        }

        leaf scope {
          type enumeration {
            enum global;
            enum local;
          }
        }

        leaf family {
          type stypes:ip-family;
        }
      }
      /* end of VLAN_INTERFACE_LIST */
    }
    /* end of VLAN_INTERFACE container */
  }
  /* end of container sonic-vlan */
}
/* end of module sonic-vlan */
