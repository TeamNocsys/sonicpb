module accton-lldp {

  yang-version 1.1;

  namespace "http://github.com/accton/sonic-yang/accton-lldp";
  prefix lldp;

  import ietf-yang-types {
    prefix yang;
  }

  import accton-types {
    prefix stypes;
    revision-date 2021-02-22;
  }

  import accton-port {
    prefix port;
    revision-date 2021-02-22;
  }

  description "LLDP yang Module for SONiC OS";

  revision 2021-02-22 {
    description "First Revision";
  }

  container accton-lldp {
    container lldp {
      list lldp-list {
        key "port-name";
        
        leaf port-name {
          type leafref {
            path /port:accton-port/port:port/port:port-list/port:port-name;
          }
        }
        
        container state {
          leaf lldp_rem_port_desc {
            type string {
              length 0..255;
            }
          }
          
          leaf lldp_rem_port_id {
            type string {
              length 1..255;
            }
          }
          
          leaf lldp_rem_port_id_subtype {
            type enumeration {
              enum IFALIAS;
              enum PORT;
              enum LLADDR;
              enum ADDR;
              enum IFNAME;
              enum AGENTCID;
              enum LOCAL;
            }
          }
          
          leaf lldp_rem_man_addr {
            type string {
              length 1..128;
            }
          }
          
          leaf lldp_rem_time_mark {
            type yang:timestamp;
          }
          
          leaf lldp_rem_chassis_id_subtype {
            type enumeration {
              enum CHASSIS;
              enum IFALIAS;
              enum PORT;
              enum LLADDR;
              enum ADDR;
              enum IFNAME;
              enum LOCAL;
            }
          }
          
          leaf lldp_rem_sys_cap_enabled {
            /*type bits {
              bit other {
                position 0;
              }
              
              bit repeater {
                position 1;
              }
      
              bit bridge {
                position 2;
              }
      
              bit wlan-access-point {
                position 3;
              }
      
              bit router {
                position 4;
              }
      
              bit telephone {
                position 5;
              }
      
              bit docsis-cable-device {
                position 6;
              }
      
              bit station-only {
                position 7;
              }
            }*/
            type uint32;
          }
          
          leaf lldp_rem_sys_name {
            type string {
              length 0..255;
            }
          }
          
          leaf lldp_rem_chassis_id {
            type string;
          }
          
          leaf lldp_rem_index {
            type uint32;
          }
          
          leaf lldp_rem_sys_desc {
            type string {
              length 0..255;
            }
          }
          
          leaf lldp_rem_sys_cap_supported {
            //type stypes:lldp-system-capability;
            type uint32;
          }
        }
      }
    }
  }
}
