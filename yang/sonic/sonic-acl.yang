module sonic-acl {

	yang-version 1.1;

	namespace "http://github.com/Azure/sonic-acl";
	prefix acl;

	import ietf-yang-types {
		prefix yang;
	}

	import ietf-inet-types {
		prefix inet;
	}

	import sonic-types {
		prefix stypes;
		revision-date 2019-07-01;
	}

	import sonic-extension {
		prefix ext;
		revision-date 2019-07-01;
	}

	import sonic-port {
		prefix port;
		revision-date 2019-07-01;
	}

	import sonic-portchannel {
		prefix lag;
		revision-date 2019-07-01;
	}

	description "ACL YANG Module for SONiC OS";

	revision 2019-07-01 {
		description "First Revision";
	}

	container sonic-acl {

		container acl-rule {

			description "ACL_RULE part of config_db.json";

			list acl-rule-list {

				key "acl-table-name rule-name";

				ext:key-regex-configdb-to-yang "^([a-zA-Z0-9_-]+)|([a-zA-Z0-9_-]+)$";

				ext:key-regex-yang-to-configdb "<acl-table-name>|<rule-name>";

				leaf acl-table-name {
					type leafref {
						path "/acl:sonic-acl/acl:acl-table/acl:acl-table-list/acl:acl-table-name";
					}
				}

				leaf rule-name {
					type string {
						length 1..255;
					}
				}

				leaf packet-action {
					type stypes:packet-action;
				}

				leaf ip-type {
					type stypes:ip-type;
				}

				leaf priority {
					type uint32 {
						range 0..999999;
					}
				}

				choice ip-prefix {

					case ip4-prefix {
						when "boolean(ip-type[.='ANY' or .='IP' or .='IPV4' or .='IPv4ANY' or .='ARP'])";
						leaf src-ip {
							type inet:ipv4-prefix;
						}

						leaf dst-ip {
							type inet:ipv4-prefix;
						}
					}

					case ip6-prefix {
						when "boolean(ip-type[.='ANY' or .='IP' or .='IPV6' or .='IPv6ANY'])";
						leaf src_ip6 {
							type inet:ipv6-prefix;
						}

						leaf dst-ip6 {
							type inet:ipv6-prefix;
						}
					}
				}

				leaf-list in-ports {
					/* Values in leaf list are UNIQUE */
					type uint16;
				}

				leaf-list out-ports {
					/* Values in leaf list are UNIQUE */
					type uint16;
				}

				choice src-port {
					case l4-src-port {
						leaf l4-src-port {
							type uint16;
						}
					}

					case l4-src-port-range {
						leaf l4-src-port-range {
							type string {
								pattern '([0-9]{1,4}|[0-5][0-9]{4}|[6][0-4][0-9]{3}|[6][5][0-2][0-9]{2}|[6][5][3][0-5]{2}|[6][5][3][6][0-5])-([0-9]{1,4}|[0-5][0-9]{4}|[6][0-4][0-9]{3}|[6][5][0-2][0-9]{2}|[6][5][3][0-5]{2}|[6][5][3][6][0-5])';
							}
						}
					}
				}

				choice dst-port {
					case l4-dst-port {
						leaf l4-dst-port {
							type uint16;
						}
					}

					case l4_dst_port_range {
						leaf L4_DST_PORT_RANGE {
							type string {
								pattern '([0-9]{1,4}|[0-5][0-9]{4}|[6][0-4][0-9]{3}|[6][5][0-2][0-9]{2}|[6][5][3][0-5]{2}|[6][5][3][6][0-5])-([0-9]{1,4}|[0-5][0-9]{4}|[6][0-4][0-9]{3}|[6][5][0-2][0-9]{2}|[6][5][3][0-5]{2}|[6][5][3][6][0-5])';
							}
						}
					}
				}

				leaf ether-type {
					type string {
						pattern "(0x88CC|0x8100|0x8915|0x0806|0x0800|0x86DD|0x8847)";
					}
				}

				leaf ip-protocol {
					type uint8 {
						range 1..143;
					}
				}

				leaf tcp-flags {
					type string {
						pattern '0[x][0-9a-fA-F]{1,2}|0[X][0-9a-fA-F]{1,2}';
					}
				}

				leaf dscp {
					type uint8;
				}

				leaf tc {
					type uint8;
				}

				choice icmp {

					case icmp4 {
						when "boolean(ip-type[.='ANY' or .='IP' or .='IPV4' or .='IPv4ANY' or .='ARP'])";
						leaf icmp-type {
							type uint8 {
								range 1..44;
							}
						}

						leaf icmp-code {
							type uint8 {
								range 1..16;
							}
						}
					}

					case icmp6 {
						when "boolean(ip-type[.='ANY' or .='IP' or .='IPV6' or .='IPv6ANY'])";
						leaf icmpv6-type {
							type uint8 {
								range 1..44;
							}
						}

						leaf icmpv6-code {
							type uint8 {
								range 1..16;
							}
						}
					}
				}

				leaf inner-ether-type {
					type string {
						pattern "(0x88CC|0x8100|0x8915|0x0806|0x0800|0x86DD|0x8847)";
					}
				}

				leaf inner-ip-protocol {
					type uint8 {
						range 1..143;
					}
				}

				leaf inner-l4-src-port {
					type uint16;
				}

				leaf inner-l4-dst-port {
					type uint16;
				}
			}
			/* end of ACL_RULE_LIST */
		}
		/* end of container ACL_RULE */

		container acl-table {

			description "ACL_TABLE part of config_db.json";

			list acl-table-list {

				key "acl-table-name";

				ext:key-regex-configdb-to-yang "^([a-zA-Z0-9-_]+)$";

				ext:key-regex-yang-to-configdb "<acl-table-name>";

				leaf acl-table-name {
					type string;
				}

				leaf policy-desc {
					type string {
						length 1..255;
					}
				}

				leaf type {
					type stypes:acl-table-type;
				}

				leaf stage {
					type enumeration {
						enum INGRESS;
						enum EGRESS;
					}
				}

				leaf-list ports {
                    /* union of leafref is allowed in YANG 1.1 */
					type union {
						type leafref {
							path /port:sonic-port/port:port/port:port-list/port:port-name;
						}
						type leafref {
							path /lag:sonic-portchannel/lag:portchannel/lag:portchannel-list/lag:portchannel-name;
						}
					}
				}
			}
			/* end of ACL_TABLE_LIST */
		}
        /* end of container ACL_TABLE */
	}
    /* end of container sonic-acl */
}
/* end of module sonic-acl */
